module bgp-operational {

     yang-version "1";

     // namespace
     // TODO: change to an ietf or other more generic namespace
     namespace "http://google.com/yang/google-bgp-operational";

     prefix "bgp-op";

     // import some basic inet types
     import ietf-inet-types { prefix inet; }
     // meta

     organization
       "Google, AT&T, BT, Microsoft";

     contact
       "Google, Inc.
       1600 Amphitheatre Way
       Mountain View, CA  94043

       AT&T Labs
       200 S. Laurel Avenue
       Middletown, NJ  07748

       BT
       pp. C3L, BT Centre
       81, Newgate Street
       London  EC1A 7AJ
       UK

       Microsoft
       205 108th Ave. NE, Suite 400
       Bellevue, WA 98004";

     description
       "This module is part of a YANG model for BGP protocol
       configuration, focusing on operational data (i.e., state
       variables) related to BGP operations";

     revision "2014-10-13" {
       description
         "Initial revision";
       reference "TBD";
     }

     // extension statements

     // feature statements

     // identity statements

     // typedef statements

     // grouping statements

     grouping bgp-op-global-group {
       description
         "top level container for operational state data";

       container bgp-global-state {
         config false;
         description
           "data definitions for operational state variables related
           to the global BGP instance";
       }
     }

     grouping bgp-op-af-group {
       description
         "top level container for operational state data";

       container bgp-af-common-state {
         config false;
         description
           "data definitions for operational state variables related
           to all BGP address families instance";
       }
     }

     grouping bgp-op-peergroup-group {
       description
         "top level container for operational state data";

       container bgp-group-common-state {
         config false;
         description
           "data definitions for operational state variables related
           to BGP peer groups";
       }
     }

     grouping bgp-op-neighbor-group {
       description
         "top level container for operational state data";

       container bgp-neighbor-common-state {
         config false;
         description
           "data definitions for operational state variables related
           to BGP neighbor sesions";
       }
     }

     // data definition statements
     // augment statements

     // rpc statements

     // notification statements
   }
